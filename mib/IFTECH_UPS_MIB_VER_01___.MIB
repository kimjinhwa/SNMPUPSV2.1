IFTECH_UPS-MIB_VER01    DEFINITIONS ::= BEGIN
IMPORTS
	RowStatus, DisplayString, DateAndTime
		FROM SNMPv2-TC
	DisplayString
		FROM RFC1213-MIB
	enterprises, MODULE-IDENTITY, OBJECT-TYPE, Unsigned32, IpAddress, NOTIFICATION-TYPE, Integer32
		FROM SNMPv2-SMI;
		
	moduleIdentity	MODULE-IDENTITY
	LAST-UPDATED    "201408141141"
	ORGANIZATION    "IFTECH FOR UPS"
	CONTACT-INFO    "mvcjhkim@gmail.com"
	DESCRIPTION       "for common ups"
	REVISION             "201702011300"
	DESCRIPTION       "Description"
	::=  {  mgmt  1  }	

	upsCommon	OBJECT IDENTIFIER
		::=  {  mgmt  1  }

	upsStatus	OBJECT IDENTIFIER
		::=  {  upsCommon  33  }

	upsValue	OBJECT IDENTIFIER
		::=  {  upsStatus  1  }

	upsMeasure	OBJECT IDENTIFIER
		::=  {  upsValue  1  }

	Year_made        OBJECT-TYPE	
		SYNTAX			Integer32
		MAX-ACCESS		read-write
		STATUS			current
		DESCRIPTION		"Manufactured Year"
		::=  {  upsMeasure  1  }

	Month_made        OBJECT-TYPE	
		SYNTAX			Integer32
		MAX-ACCESS		read-write
		STATUS			current
		DESCRIPTION		"Manufactured month"
		::=  {  upsMeasure  2  }

	Date_made        OBJECT-TYPE	
		SYNTAX			Integer32
		MAX-ACCESS		read-write
		STATUS			current
		DESCRIPTION		"Manufactured month"
		::=  {  upsMeasure  3  }

	Ups_Capacitor        OBJECT-TYPE	
		SYNTAX			Integer32
		MAX-ACCESS		read-write
		STATUS			current
		DESCRIPTION		"Ups_Capacitor"
		::=  {  upsMeasure  4  }

	Input_Phase        OBJECT-TYPE	
		SYNTAX			Integer32
		MAX-ACCESS		read-write
		STATUS			current
		DESCRIPTION		"Input_Phase"
		::=  {  upsMeasure  5  }

	Input_Voltage        OBJECT-TYPE	
		SYNTAX			Integer32
		MAX-ACCESS		read-write
		STATUS			current
		DESCRIPTION		"Input_Voltage"
		::=  {  upsMeasure  6  }

	Output_Phase        OBJECT-TYPE	
		SYNTAX			Integer32
		MAX-ACCESS		read-write
		STATUS			current
		DESCRIPTION		"Output_Phase"
		::=  {  upsMeasure  7  }

	Output_Voltage        OBJECT-TYPE	
		SYNTAX			Integer32
		MAX-ACCESS		read-write
		STATUS			current
		DESCRIPTION		"Output_Voltage"
		::=  {  upsMeasure  8  }

	Company_code_And_upstype        OBJECT-TYPE	
		SYNTAX			Integer32
		MAX-ACCESS		read-write
		STATUS			current
		DESCRIPTION		"Company_code_And_upstype,  High 8 BIT Check ,0x01xx  IFTECH,  0x02xx  HANUPS,0x03xx  SUNGSIN,0x04xx  DAENONG,0x05xx  XEONICS,0x06xx  DAEHAN,
		0x07xx  영신엔지니어링, 0xxx0A NEP 3P3P, 0xxx0B NEP 3P1P"
		::=  {  upsMeasure  9  }

	Installed_Battery_Cells        OBJECT-TYPE	
		SYNTAX			Integer32
		MAX-ACCESS		read-write
		STATUS			current
		DESCRIPTION		"Installed_Battery_Cells"
		::=  {  upsMeasure  10  }

	reserved_2        OBJECT-TYPE	
		SYNTAX			Integer32
		MAX-ACCESS		read-write
		STATUS			current
		DESCRIPTION		"reserved_2"
		::=  {  upsMeasure  11  }

	BMS_1_2_STATE        OBJECT-TYPE	
		SYNTAX			Integer32
		MAX-ACCESS		read-write
		STATUS			current
		DESCRIPTION		"BMS_1_2_STATE"
		::=  {  upsMeasure  12  }

	Converter_State        OBJECT-TYPE	
		SYNTAX			Integer32
		MAX-ACCESS		read-write
		STATUS			current
		DESCRIPTION		"Converter_State"
		::=  {  upsMeasure  13  }

	Inverter_State        OBJECT-TYPE	
		SYNTAX			Integer32
		MAX-ACCESS		read-write
		STATUS			current
		DESCRIPTION		"Inverter_State"
		::=  {  upsMeasure  14  }

	Converter_Operation_Fault        OBJECT-TYPE	
		SYNTAX			Integer32
		MAX-ACCESS		read-write
		STATUS			current
		DESCRIPTION		"Converter_Operation_Fault"
		::=  {  upsMeasure  15  }

	Inverter_Operation_Fault        OBJECT-TYPE	
		SYNTAX			Integer32
		MAX-ACCESS		read-write
		STATUS			current
		DESCRIPTION		"Inverter_Operation_Fault"
		::=  {  upsMeasure  16  }

	Input_r_volt_rms        OBJECT-TYPE	
		SYNTAX			Integer32
		MAX-ACCESS		read-write
		STATUS			current
		DESCRIPTION		"Input_r_volt_rms"
		::=  {  upsMeasure  17  }

	Input_s_volt_rms        OBJECT-TYPE	
		SYNTAX			Integer32
		MAX-ACCESS		read-write
		STATUS			current
		DESCRIPTION		"Input_s_volt_rms"
		::=  {  upsMeasure  18  }

	Input_t_volt_rms        OBJECT-TYPE	
		SYNTAX			Integer32
		MAX-ACCESS		read-write
		STATUS			current
		DESCRIPTION		"Input_t_volt_rms"
		::=  {  upsMeasure  19  }

	Input_r_current_rms        OBJECT-TYPE	
		SYNTAX			Integer32
		MAX-ACCESS		read-write
		STATUS			current
		DESCRIPTION		"Input_r_current_rms"
		::=  {  upsMeasure  20  }

	Input_s_current_rms        OBJECT-TYPE	
		SYNTAX			Integer32
		MAX-ACCESS		read-write
		STATUS			current
		DESCRIPTION		"Input_s_current_rms"
		::=  {  upsMeasure  21  }

	Input_t_current_rms        OBJECT-TYPE	
		SYNTAX			Integer32
		MAX-ACCESS		read-write
		STATUS			current
		DESCRIPTION		"Input_t_current_rms"
		::=  {  upsMeasure  22  }

	Input_frequency        OBJECT-TYPE	
		SYNTAX			Integer32
		MAX-ACCESS		read-write
		STATUS			current
		DESCRIPTION		"Input_frequency"
		::=  {  upsMeasure  23  }

	Bypass_r_volt_rms        OBJECT-TYPE	
		SYNTAX			Integer32
		MAX-ACCESS		read-write
		STATUS			current
		DESCRIPTION		"Bypass_r_volt_rms"
		::=  {  upsMeasure  24  }

	Bypass_s_volt_rms        OBJECT-TYPE	
		SYNTAX			Integer32
		MAX-ACCESS		read-write
		STATUS			current
		DESCRIPTION		"Bypass_s_volt_rms"
		::=  {  upsMeasure  25  }

	Bypass_t_volt_rms        OBJECT-TYPE	
		SYNTAX			Integer32
		MAX-ACCESS		read-write
		STATUS			current
		DESCRIPTION		""
		::=  {  upsMeasure  26  }

	Bypass_r_current_rms        OBJECT-TYPE	
		SYNTAX			Integer32
		MAX-ACCESS		read-write
		STATUS			current
		DESCRIPTION		"Bypass_t_volt_rms"
		::=  {  upsMeasure  27  }

	Bypass_s_current_rms        OBJECT-TYPE	
		SYNTAX			Integer32
		MAX-ACCESS		read-write
		STATUS			current
		DESCRIPTION		"Bypass_s_current_rms"
		::=  {  upsMeasure  28  }

	Bypass_t_current_rms        OBJECT-TYPE	
		SYNTAX			Integer32
		MAX-ACCESS		read-write
		STATUS			current
		DESCRIPTION		"Bypass_t_current_rms"
		::=  {  upsMeasure  29  }

	Bypass_Frequency        OBJECT-TYPE	
		SYNTAX			Integer32
		MAX-ACCESS		read-write
		STATUS			current
		DESCRIPTION		"Bypass_Frequency"
		::=  {  upsMeasure  30  }

	Inverter_u_volt_rms        OBJECT-TYPE	
		SYNTAX			Integer32
		MAX-ACCESS		read-write
		STATUS			current
		DESCRIPTION		"Inverter_u_volt_rms"
		::=  {  upsMeasure  31  }

	Inverter_v_volt_rms        OBJECT-TYPE	
		SYNTAX			Integer32
		MAX-ACCESS		read-write
		STATUS			current
		DESCRIPTION		"Inverter_v_volt_rms"
		::=  {  upsMeasure  32  }

	Inverter_w_volt_rms        OBJECT-TYPE	
		SYNTAX			Integer32
		MAX-ACCESS		read-write
		STATUS			current
		DESCRIPTION		"Inverter_w_volt_rms"
		::=  {  upsMeasure  33  }

	Inverter_u_curr_rms        OBJECT-TYPE	
		SYNTAX			Integer32
		MAX-ACCESS		read-write
		STATUS			current
		DESCRIPTION		"Inverter_u_curr_rms"
		::=  {  upsMeasure  34  }

	Inverter_V_curr_rms        OBJECT-TYPE	
		SYNTAX			Integer32
		MAX-ACCESS		read-write
		STATUS			current
		DESCRIPTION		"Inverter_V_curr_rms"
		::=  {  upsMeasure  35  }

	Inverter_W_curr_rms        OBJECT-TYPE	
		SYNTAX			Integer32
		MAX-ACCESS		read-write
		STATUS			current
		DESCRIPTION		"Inverter_W_curr_rms"
		::=  {  upsMeasure  36  }

	Inverter_Frequency        OBJECT-TYPE	
		SYNTAX			Integer32
		MAX-ACCESS		read-write
		STATUS			current
		DESCRIPTION		"Inverter_Frequency"
		::=  {  upsMeasure  37  }

	Bat_volt_rms        OBJECT-TYPE	
		SYNTAX			Integer32
		MAX-ACCESS		read-write
		STATUS			current
		DESCRIPTION		"Bat_volt_rms"
		::=  {  upsMeasure  38  }

	Bat_current_rms        OBJECT-TYPE	
		SYNTAX			Integer32
		MAX-ACCESS		read-write
		STATUS			current
		DESCRIPTION		"Bat_current_rms"
		::=  {  upsMeasure  39  }

	Input_kva_address_KVA        OBJECT-TYPE	
		SYNTAX			Integer32
		MAX-ACCESS		read-write
		STATUS			current
		DESCRIPTION		"Input_kva_address_KVA"
		::=  {  upsMeasure  40  }

	Input_kw_KW        OBJECT-TYPE	
		SYNTAX			Integer32
		MAX-ACCESS		read-write
		STATUS			current
		DESCRIPTION		"Input_kw_KW"
		::=  {  upsMeasure  41  }

	Input_kvar_KVAR        OBJECT-TYPE	
		SYNTAX			Integer32
		MAX-ACCESS		read-write
		STATUS			current
		DESCRIPTION		"Input_kvar_KVAR"
		::=  {  upsMeasure  42  }

	Input_power_factor_Pf        OBJECT-TYPE	
		SYNTAX			Integer32
		MAX-ACCESS		read-write
		STATUS			current
		DESCRIPTION		"Input_power_factor_Pf"
		::=  {  upsMeasure  43  }

	Output_r_volt_rms        OBJECT-TYPE	
		SYNTAX			Integer32
		MAX-ACCESS		read-write
		STATUS			current
		DESCRIPTION		"Output_r_volt_rms"
		::=  {  upsMeasure  44  }

	Output_s_volt_rms        OBJECT-TYPE	
		SYNTAX			Integer32
		MAX-ACCESS		read-write
		STATUS			current
		DESCRIPTION		"Output_s_volt_rms"
		::=  {  upsMeasure  45  }

	Output_t_volt_rms        OBJECT-TYPE	
		SYNTAX			Integer32
		MAX-ACCESS		read-write
		STATUS			current
		DESCRIPTION		"Output_t_volt_rms"
		::=  {  upsMeasure  46  }

	Output_u_current_rms        OBJECT-TYPE	
		SYNTAX			Integer32
		MAX-ACCESS		read-write
		STATUS			current
		DESCRIPTION		"Output_u_current_rms"
		::=  {  upsMeasure  47  }

	Output_v_current_rms        OBJECT-TYPE	
		SYNTAX			Integer32
		MAX-ACCESS		read-write
		STATUS			current
		DESCRIPTION		"Output_v_current_rms"
		::=  {  upsMeasure  48  }

	Output_w_current_rms        OBJECT-TYPE	
		SYNTAX			Integer32
		MAX-ACCESS		read-write
		STATUS			current
		DESCRIPTION		"Output_w_current_rms"
		::=  {  upsMeasure  49  }

	Output_frequency        OBJECT-TYPE	
		SYNTAX			Integer32
		MAX-ACCESS		read-write
		STATUS			current
		DESCRIPTION		"Output_frequency"
		::=  {  upsMeasure  50  }

	Output_kva_KVA        OBJECT-TYPE	
		SYNTAX			Integer32
		MAX-ACCESS		read-write
		STATUS			current
		DESCRIPTION		"Output_kva_KVA"
		::=  {  upsMeasure    51}

	Output_kw_KW        OBJECT-TYPE	
		SYNTAX			Integer32
		MAX-ACCESS		read-write
		STATUS			current
		DESCRIPTION		"Output_kw_KW"
		::=  {  upsMeasure  52  }

	Output_kvar_KVAR        OBJECT-TYPE	
		SYNTAX			Integer32
		MAX-ACCESS		read-write
		STATUS			current
		DESCRIPTION		"Output_kvar_KVAR"
		::=  {  upsMeasure  53  }

	Output_Power_factor_Pf        OBJECT-TYPE	
		SYNTAX			Integer32
		MAX-ACCESS		read-write
		STATUS			current
		DESCRIPTION		"Output_Power_factor_Pf"
		::=  {  upsMeasure  54  }

	Output_R_Load        OBJECT-TYPE	
		SYNTAX			Integer32
		MAX-ACCESS		read-write
		STATUS			current
		DESCRIPTION		"Output_R_Load"
		::=  {  upsMeasure  55  }

	Output_S_Load        OBJECT-TYPE	
		SYNTAX			Integer32
		MAX-ACCESS		read-write
		STATUS			current
		DESCRIPTION		"Output_S_Load"
		::=  {  upsMeasure  56  }

	Output_T_Load        OBJECT-TYPE	
		SYNTAX			Integer32
		MAX-ACCESS		read-write
		STATUS			current
		DESCRIPTION		"Output_T_Load"
		::=  {  upsMeasure  57  }

	BMS_Bat_Voltage        OBJECT-TYPE	
		SYNTAX			Integer32
		MAX-ACCESS		read-write
		STATUS			current
		DESCRIPTION		"BMS_Bat_Voltage"
		::=  {  upsMeasure  58  }

	Battery_Room_Temper        OBJECT-TYPE	
		SYNTAX			Integer32
		MAX-ACCESS		read-write
		STATUS			current
		DESCRIPTION		"Battery_Room_Temper"
		::=  {  upsMeasure  58  }

	Get_All_Data        OBJECT-TYPE	
		SYNTAX			Integer32
		MAX-ACCESS		read-write
		STATUS			current
		DESCRIPTION		"Get All Data from 1-58 "
		::=  {  upsMeasure  60  }

		
	iftech	OBJECT IDENTIFIER
		::=  {  enterprises  12236  }
		
	KEP_UPS OBJECT IDENTIFIER
		::=  {  iftech  2  }
	
	KEP_CODE OBJECT IDENTIFIER
		::=  {  KEP_UPS  12082  }

		
	inputVoltage_R        OBJECT-TYPE	
		SYNTAX			Integer32
		MAX-ACCESS		read-write
		STATUS			current
		DESCRIPTION		"inputVoltage_R "
		::=  {  KEP_CODE  1  }

	inputVoltage_S                  OBJECT-TYPE	
		SYNTAX			Integer32
		MAX-ACCESS		read-write
		STATUS			current
		DESCRIPTION		"inputVoltage_S"
		::=  {  KEP_CODE  2  }	
		
	inputVoltage_T                     OBJECT-TYPE	
		SYNTAX			Integer32
		MAX-ACCESS		read-write
		STATUS			current
		DESCRIPTION		" inputVoltage_T"
		::=  {  KEP_CODE 3  }
		
	outputVoltage                     OBJECT-TYPE	
		SYNTAX			Integer32
		MAX-ACCESS		read-write
		STATUS			current
		DESCRIPTION		"outputVoltage"
		::=  {  KEP_CODE  4  }
		
	outputCurrent                     OBJECT-TYPE	
		SYNTAX			Integer32
		MAX-ACCESS		read-write
		STATUS			current
		DESCRIPTION		"outputCurrent"
		::=  {  KEP_CODE  5  }

	batteryVoltage                     OBJECT-TYPE	
		SYNTAX			Integer32
		MAX-ACCESS		read-write
		STATUS			current
		DESCRIPTION		"batteryVoltage"
		::=  {  KEP_CODE  6  }

	chargeCurrent                     OBJECT-TYPE	
		SYNTAX			Integer32
		MAX-ACCESS		read-write
		STATUS			current
		DESCRIPTION		"chargeCurrent"
		::=  {  KEP_CODE  7  }

	chargeMode                     OBJECT-TYPE	
		SYNTAX			Integer32
		MAX-ACCESS		read-write
		STATUS			current
		DESCRIPTION		"chargeMode"
		::=  {  KEP_CODE  8  }

	outputFrequency                     OBJECT-TYPE	
		SYNTAX			Integer32
		MAX-ACCESS		read-write
		STATUS			current
		DESCRIPTION		"outputFrequency"
		::=  {  KEP_CODE  9  }

	powerFail                     OBJECT-TYPE	
		SYNTAX			Integer32
		MAX-ACCESS		read-write
		STATUS			current
		DESCRIPTION		"powerFail"
		::=  {  KEP_CODE  200  }

	powerFail_Recover                     OBJECT-TYPE	
		SYNTAX			Integer32
		MAX-ACCESS		read-write
		STATUS			current
		DESCRIPTION		"powerFail_Recover"
		::=  {  KEP_CODE  201  }
	
	inputpowerFail                     OBJECT-TYPE	
		SYNTAX			Integer32
		MAX-ACCESS		read-write
		STATUS			current
		DESCRIPTION		"inputpowerFail"
		::=  {  KEP_CODE  202  }

	inputpowerFail_Recover                     OBJECT-TYPE	
		SYNTAX			Integer32
		MAX-ACCESS		read-write
		STATUS			current
		DESCRIPTION		"inputpowerFail_Recover"
		::=  {  KEP_CODE  203  }

	module1_Fail                     OBJECT-TYPE	
		SYNTAX			Integer32
		MAX-ACCESS		read-write
		STATUS			current
		DESCRIPTION		"module1_Fail"
		::=  {  KEP_CODE  210  }

	module1_Fail_Recover                     OBJECT-TYPE	
		SYNTAX			Integer32
		MAX-ACCESS		read-write
		STATUS			current
		DESCRIPTION		"module1_Fail_Recover"
		::=  {  KEP_CODE  211  }

	module2_Fail                     OBJECT-TYPE	
		SYNTAX			Integer32
		MAX-ACCESS		read-write
		STATUS			current
		DESCRIPTION		"module2_Fail"
		::=  {  KEP_CODE  212  }

	module2_Fail_Recover                     OBJECT-TYPE	
		SYNTAX			Integer32
		MAX-ACCESS		read-write
		STATUS			current
		DESCRIPTION		"module2_Fail_Recover"
		::=  {  KEP_CODE  213  }

	module3_Fail                     OBJECT-TYPE	
		SYNTAX			Integer32
		MAX-ACCESS		read-write
		STATUS			current
		DESCRIPTION		"module3_Fail"
		::=  {  KEP_CODE  214  }

	module3_Fail_Recover                     OBJECT-TYPE	
		SYNTAX			Integer32
		MAX-ACCESS		read-write
		STATUS			current
		DESCRIPTION		"module3_Fail_Recover"
		::=  {  KEP_CODE  215  }

	module4_Fail                     OBJECT-TYPE	
		SYNTAX			Integer32
		MAX-ACCESS		read-write
		STATUS			current
		DESCRIPTION		"module4_Fail"
		::=  {  KEP_CODE  216  }

	module4_Fail_Recover                     OBJECT-TYPE	
		SYNTAX			Integer32
		MAX-ACCESS		read-write
		STATUS			current
		DESCRIPTION		"module4_Fail_Recover"
		::=  {  KEP_CODE  217  }

END
